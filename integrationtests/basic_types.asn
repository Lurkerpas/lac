Test DEFINITIONS ::=
BEGIN

UInt8 ::= INTEGER(0..255)
Int16 ::= INTEGER(-32768..32767)

Bool8 ::= BOOLEAN

Float32 ::= REAL(-100.0..100.0)

Values ::= ENUMERATED {
    val1 (1),
    val2 (2),
    val3 (4) 
}

END
